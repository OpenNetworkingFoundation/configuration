module ndm {
  namespace "urn:opennetworking.org:yang:ndm";
  prefix ndm;

  import of-config { prefix ofc; }

  organization "ONF Config Management Group";

  contact "mailto:info@opennetworking.org";

  description
    "This module contains a collection of data definitions related to
     Negotiated Datapath Models (NDMs) and consists only of augments
     to the main OF-CONFIG module.

     This module provides a basic structure for NDMs. Modules for
     specific NDMs are expected to further ugment this module with
     data definitions related to the specific NDM.

     This module is part of the OF-CONFIG specification.";

  revision 2013-10-05 {
    description
       "This version of this YANG Module is part of the OF-CONFIG
        1.2 specification; please see the specification itself for
        details.";

    reference
      "OF-CONFIG 1.2";    
  }

/*****************************************************************
 * Augments
 *****************************************************************/

  augment "/ofc:capable-switch/ofc:resources" {
    container ndm {
      presence "This swith supports NDMs";
      config false;

      description
	"The container for the capable-switch global list of available
         NDMs.";

      list available-ndms {
	description
	  "The list of all NDMs implemented by the capable-switch

           Clients can query this list to learn about supported
           NDMs before implementing them on logical-switches";

	leaf name {
	  mandatory true;
	  type string;

	  description
	    "A unique name of the NDM.

             This name corresponds to the 'ndm-implementation-choice'
             name per logical-switch. Clients are expected to:
              - Find out about available NDMs by querying this list;
              - and configure specific NDM implementations per logical-switch
                using this name";
	}
    
	leaf type {
	  mandatory true;
	  type enumeration {
	    enum ttp;
	    enum fpmod;
	  }

	  description
	    "The NDM type.";
	}

	leaf version {
	  mandatory true;
	  type string;

	  description
	    "The version of this named NDM.";
	}
      }
    }
  }

  augment "/ofc:capable-switch/ofc:logical-switches/ofc:switch/ofc:resources" {
    container ndm-implementation {
      choice ndm-implementation-choice {
	description
	  "This is the choice-construct for configuring specific NDM
           implementations on a logical switch

           Specific NDM implementations augment this choice with new cases
           with the same name as the corresponding 'available-ndm'";
      }
    }
  }
}
