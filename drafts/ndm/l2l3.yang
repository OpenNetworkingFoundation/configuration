module l2l3 {

  namespace "urn:opennetworking.org:yang:ndm:l2l3";
  prefix "l2l3";

  import of-config {
    prefix ofc;
  }

  import ndm {
    prefix ndm;
  }

  augment "/ofc:capable-switch/ofc:logical-switches/ofc:switch/ofc:resources/ndm:ndm-implementation/ndm:ndm-implementation-choice" {
    case l2l3 {
      container l2l3 {
	leaf ingress-vlan-table-size {
	  type uint32;
	}

	leaf router-mac-table-size {
	  type uint32;
	}

	leaf l3-table-size {
	  type uint32;
	}

	leaf l2-table-size {
	  type uint32;
	}

	leaf egress-vlan-table-size {
	  type uint32;
	}

	leaf l3-counters {
	  type boolean;
	  default true;
	}

	leaf l2-counters {
	  type boolean;
	  default true;
	}

	leaf ipv6-supported {
	  config false;
	  type boolean;
	}
      }
    }
  }
}
